# Smart Coffee Machine
Fictional sample data for demonstration

# Specification: System Requirements

## H1: General (Heading)

### SYS-001 (Requirement)
The machine shall brew a 200 ml cup of coffee in less than 60 seconds.
- Priority: High
- Status: Approved
- Verification Method: Test

### SYS-002 (Requirement)
The machine shall support the following drink types:
- Espresso
- Americano
- Cappuccino
- Priority: High
- Status: Approved
- Verification Method: Inspection

## H2: Safety (Heading)

### SYS-003 (Requirement)
The heater shall switch off automatically when the water tank is empty.
- Priority: High
- Status: Approved
- Verification Method: Test

### SYS-004 (Requirement)
The outer surface temperature shall not exceed 45 °C during operation.
- Priority: Medium
- Status: Draft
- Verification Method: Analysis

## H3: Connectivity (Heading)

### SYS-005 (Requirement)
The machine shall be controllable from a mobile app over Wi-Fi.
- Priority: Low
- Status: Draft
- Verification Method: Test

# Specification: Software Requirements

## SW-001 (Requirement)
The controller software shall stop the brewing cycle after 55 seconds at the latest.
- Priority: High
- Status: Approved
- Verification Method: Test
- Refines -> SYS-001

## SW-002 (Requirement)
The software shall read the water level sensor every 100 ms.
- Priority: High
- Status: Approved
- Verification Method: Test
- Refines -> SYS-003

## SW-003 (Requirement)
The app API shall require user authentication before any command is accepted.
- Priority: Medium
- Status: Draft
- Verification Method: Inspection
- Refines -> SYS-005
